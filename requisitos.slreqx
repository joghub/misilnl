# requisitos

## Velocidad de subida (Functional)
El misil tiene que ser capaz de subir a cierto nivel de vuelo en menos de x tiempo.
Verificar en Test
- Keywords: velocidad subida misil nivel de vuelo

## Alcance: Alcance mínimo (Functional)
El misil tiene que ser capaz de superar cierto distancia horizontal para cierto tiempo de empuje máximo.
- Keywords: alcance, missile range

## #4: Altura de vuelo (Functional)
Capacidad de vuelo a una altura de operación de (X,X) m
- Keywords: Altura de operación

## #5: Carga máxima (Functional)
Capacidad de volar y ser controlado con X kg de carga
- Keywords: Carga

## #6 (Functional)
